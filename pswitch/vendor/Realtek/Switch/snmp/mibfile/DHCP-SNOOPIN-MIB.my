DHCP-SNOOPING-MIB DEFINITIONS ::= BEGIN

IMPORTS
   MODULE-IDENTITY, OBJECT-TYPE,
   Integer32                                    	            FROM SNMPv2-SMI
   RTLDevice                                                     FROM REALTEK-MIB
   DisplayString                                                 FROM SNMPv2-TC;
   
dhcpSnoopingMib MODULE-IDENTITY
   LAST-UPDATED "202001110000Z"
   ORGANIZATION "realtek"
   CONTACT-INFO "realtek"
   DESCRIPTION  "Realtek MIB definition."
   REVISION     "202001110000Z"
   DESCRIPTION
      "system interfece control MIB module"
   ::= { RTLDevice 5 }


dhcpsnoopingOnOff         OBJECT-TYPE
   SYNTAX            Integer32
   MAX-ACCESS        read-write
   STATUS            current
   DESCRIPTION
	"start/stop dhcpsnooping.Default is off."
   ::= { dhcpSnoopingMib	       1 }
 
 
dhcpSnoopingVlanTable OBJECT-TYPE
        SYNTAX      SEQUENCE OF dhcpSnoopingVlanEntry
        MAX-ACCESS  not-accessible
        STATUS      current
        DESCRIPTION
            "A table that contains vlan informations of dhcpsnooping."
            --DHCPSnooping的VLAN信息表。
        ::= { dhcpSnoopingMib 2 }

dhcpSnoopingVlanEntry OBJECT-TYPE
        SYNTAX      dhcpSnoopingVlanEntry
        MAX-ACCESS  not-accessible
        STATUS      current
        DESCRIPTION
            "VLAN informations of dhcpsnooping. This is indexed
            by the vlan number."
            --DHCPSnooping的VLAN信息表，以VLAN号为索引。
        INDEX { vlanIndex }
        ::= { dhcpSnoopingVlanTable 1 }

dhcpSnoopingVlanEntry ::=
    SEQUENCE {
        vlanIndex
           INTEGER,
        vlandhcpsnoopingOnOff
           INTEGER
    }
    vlanIndex OBJECT-TYPE
        SYNTAX       INTEGER (1..4094)
        MAX-ACCESS   read-only
        STATUS       current
        DESCRIPTION
            "The Index of the vlan."
            --VLAN索引，也就是VLAN号
        ::= { dhcpSnoopingVlanEntry 1 }		
		
	vlandhcpsnoopingOnOff OBJECT-TYPE
        SYNTAX       INTEGER
        MAX-ACCESS   read-write
        STATUS current
        DESCRIPTION
            "start/stop dhcpsnooping of this vlan.Default is on." 
            --开启关闭VLAN Dhcpsnooping功能。
        ::= { dhcpSnoopingVlanEntry 2 }	

dhcpsnoopingPortTable OBJECT-TYPE
        SYNTAX      SEQUENCE OF dhcpsnoopingPortEntry
        MAX-ACCESS  not-accessible
        STATUS      current
        DESCRIPTION
            "A table that contains port informations of dhcpsnooping."
        ::= { dhcpSnoopingMib 3 }

dhcpsnoopingPortEntry OBJECT-TYPE
        SYNTAX      dhcpsnoopingPortEntry
        MAX-ACCESS  not-accessible
        STATUS      current
        DESCRIPTION
            "Port informations of dhcpsnooping. This is indexed
            by the port number."
        INDEX { portIndex }
        ::= { dhcpsnoopingPortTable 1 }
		
dhcpsnoopingPortEntry ::=
    SEQUENCE {
        portIndex
           INTEGER,
        portTrustMode
           INTEGER,
        portVerifyMacAddress
           INTEGER,
        portRateLimit
           INTEGER
    }
    portIndex OBJECT-TYPE
        SYNTAX       INTEGER
        MAX-ACCESS   read-only
        STATUS       current
        DESCRIPTION
            "The Index of the port."
        ::= { dhcpsnoopingPortEntry 1 }
	
	portTrustMode OBJECT-TYPE
	SYNTAX INTEGER {
				trust(1),
				untrust(2)
				}
    MAX-ACCESS   read-write
    STATUS       current
    DESCRIPTION
        "Port mode of dhcpsnooping.Default is untrust."
		::= { dhcpsnoopingPortEntry 2 }
	
	portVerifyMacAddress OBJECT-TYPE
		SYNTAX INTEGER {
				verify-mac-address(1),
				no-verify-mac-address(2)
				}
        MAX-ACCESS read-write
        STATUS current
        DESCRIPTION
            "the mac-address drop dhcp packets that chaddr and ethernet-source-mac  is not match "
        ::= { dhcpsnoopingPortEntry 3 }
		
	portRateLimit OBJECT-TYPE
        SYNTAX       INTEGER
        MAX-ACCESS   read-write
        STATUS       current
        DESCRIPTION
            "recv that port dhcp packets rate."
        ::= { dhcpsnoopingPortEntry 4 }
END
